SPIKE-MIB DEFINITIONS ::= BEGIN

IMPORTS
	MODULE-IDENTITY, OBJECT-TYPE, Integer32, NOTIFICATION-TYPE, Counter64
	FROM SNMPv2-SMI
;

monitoring OBJECT IDENTIFIER ::= {1 3 6 1 4 100}

loadTimeStats OBJECT IDENTIFIER ::= {monitoring 1}
loadTimeSuccessStats OBJECT IDENTIFIER ::= {monitoring 2}
loadTimeFailedStats OBJECT IDENTIFIER ::= {monitoring 3}

loadPayloadBytesStats OBJECT IDENTIFIER ::= {monitoring 4}
loadPayloadBytesBuckets OBJECT IDENTIFIER ::= {monitoring 5}
loadPayloadBytesLastN OBJECT IDENTIFIER ::= {monitoring 6}
loadPayloadBytesPct OBJECT IDENTIFIER ::= {monitoring 7}

loadPayloadLinesStats OBJECT IDENTIFIER ::= {monitoring 8}
loadPayloadLinesBuckets OBJECT IDENTIFIER ::= {monitoring 9}
loadPayloadLinesLastN OBJECT IDENTIFIER ::= {monitoring 10}
loadPayloadLinesPct OBJECT IDENTIFIER ::= {monitoring 11}

storeTimeStats OBJECT IDENTIFIER ::= {monitoring 12}
storeTimeSuccessStats OBJECT IDENTIFIER ::= {monitoring 13}
storeTimeFailedStats OBJECT IDENTIFIER ::= {monitoring 14}

storePayloadBytesStats OBJECT IDENTIFIER ::= {monitoring 15}
storePayloadBytesBuckets OBJECT IDENTIFIER ::= {monitoring 16}
storePayloadBytesLastN OBJECT IDENTIFIER ::= {monitoring 17}
storePayloadBytesPct OBJECT IDENTIFIER ::= {monitoring 18}

storePayloadLinesStats OBJECT IDENTIFIER ::= {monitoring 19}
storePayloadLinesBuckets OBJECT IDENTIFIER ::= {monitoring 20}
storePayloadLinesLastN OBJECT IDENTIFIER ::= {monitoring 21}
storePayloadLinesPct OBJECT IDENTIFIER ::= {monitoring 22}

deleteTimeStats OBJECT IDENTIFIER ::= {monitoring 23}
deleteTimeSuccessStats OBJECT IDENTIFIER ::= {monitoring 24}
deleteTimeFailedStats OBJECT IDENTIFIER ::= {monitoring 25}

loadTimeCount OBJECT-TYPE SYNTAX INTEGER ACCESS read-only STATUS mandatory ::= {loadTimeStats 0}
loadTimeMinUnitMS OBJECT-TYPE SYNTAX INTEGER ACCESS read-only STATUS mandatory ::= {loadTimeStats 1}
loadTimeMaxUintMS OBJECT-TYPE SYNTAX INTEGER ACCESS read-only STATUS mandatory ::= {loadTimeStats 2}
loadTimeSumUintMS OBJECT-TYPE SYNTAX INTEGER ACCESS read-only STATUS mandatory ::= {loadTimeStats 3}
loadTimeAvgUintMS OBJECT-TYPE SYNTAX INTEGER ACCESS read-only STATUS mandatory ::= {loadTimeStats 4}

loadTimeSuccessCount OBJECT-TYPE SYNTAX INTEGER ACCESS read-only STATUS mandatory ::= {loadTimeSuccessStats 0}
loadTimeSuccessMinUnitMS OBJECT-TYPE SYNTAX INTEGER ACCESS read-only STATUS mandatory ::= {loadTimeSuccessStats 1}
loadTimeSuccessMaxUintMS OBJECT-TYPE SYNTAX INTEGER ACCESS read-only STATUS mandatory ::= {loadTimeSuccessStats 2}
loadTimeSuccessSumUintMS OBJECT-TYPE SYNTAX INTEGER ACCESS read-only STATUS mandatory ::= {loadTimeSuccessStats 3}
loadTimeSuccessAvgUintMS OBJECT-TYPE SYNTAX INTEGER ACCESS read-only STATUS mandatory ::= {loadTimeSuccessStats 4}

loadTimeFailedCount OBJECT-TYPE SYNTAX INTEGER ACCESS read-only STATUS mandatory ::= {loadTimeFailedStats 0}
loadTimeFailedMinUnitMS OBJECT-TYPE SYNTAX INTEGER ACCESS read-only STATUS mandatory ::= {loadTimeFailedStats 1}
loadTimeFailedMaxUintMS OBJECT-TYPE SYNTAX INTEGER ACCESS read-only STATUS mandatory ::= {loadTimeFailedStats 2}
loadTimeFailedSumUintMS OBJECT-TYPE SYNTAX INTEGER ACCESS read-only STATUS mandatory ::= {loadTimeFailedStats 3}
loadTimeFailedAvgUintMS OBJECT-TYPE SYNTAX INTEGER ACCESS read-only STATUS mandatory ::= {loadTimeFailedStats 4}

loadPayloadBytesCount OBJECT-TYPE SYNTAX INTEGER ACCESS read-only STATUS mandatory ::= {loadPayloadBytesStats 0}
loadPayloadBytesMin OBJECT-TYPE SYNTAX INTEGER ACCESS read-only STATUS mandatory ::= {loadPayloadBytesStats 1}
loadPayloadBytesMax OBJECT-TYPE SYNTAX INTEGER ACCESS read-only STATUS mandatory ::= {loadPayloadBytesStats 2}
loadPayloadBytesSum OBJECT-TYPE SYNTAX INTEGER ACCESS read-only STATUS mandatory ::= {loadPayloadBytesStats 3}
loadPayloadBytesAvg OBJECT-TYPE SYNTAX INTEGER ACCESS read-only STATUS mandatory ::= {loadPayloadBytesStats 4}

loadPayloadBytesBucket-NegInf-100 OBJECT-TYPE SYNTAX Integer32 ACCESS read-only STATUS mandatory ::= {loadPayloadBytesBuckets 0}
loadPayloadBytesBucket-100-1000 OBJECT-TYPE SYNTAX Integer32 ACCESS read-only STATUS mandatory ::= {loadPayloadBytesBuckets 1}
loadPayloadBytesBucket-1000-10000 OBJECT-TYPE SYNTAX Integer32 ACCESS read-only STATUS mandatory ::= {loadPayloadBytesBuckets 2}
loadPayloadBytesBucket-10000-100000 OBJECT-TYPE SYNTAX Integer32 ACCESS read-only STATUS mandatory ::= {loadPayloadBytesBuckets 3}
loadPayloadBytesBucket-100000-Inf OBJECT-TYPE SYNTAX Integer32 ACCESS read-only STATUS mandatory ::= {loadPayloadBytesBuckets 4}

loadPayloadLinesCount OBJECT-TYPE SYNTAX INTEGER ACCESS read-only STATUS mandatory ::= {loadPayloadLinesStats 0}
loadPayloadLinesMin OBJECT-TYPE SYNTAX INTEGER ACCESS read-only STATUS mandatory ::= {loadPayloadLinesStats 1}
loadPayloadLinesMax OBJECT-TYPE SYNTAX INTEGER ACCESS read-only STATUS mandatory ::= {loadPayloadLinesStats 2}
loadPayloadLinesSum OBJECT-TYPE SYNTAX INTEGER ACCESS read-only STATUS mandatory ::= {loadPayloadLinesStats 3}
loadPayloadLinesAvg OBJECT-TYPE SYNTAX INTEGER ACCESS read-only STATUS mandatory ::= {loadPayloadLinesStats 4}

loadPayloadLinesBucket-NegInf-100 OBJECT-TYPE SYNTAX Integer32 ACCESS read-only STATUS mandatory ::= {loadPayloadLinesBuckets 0}
loadPayloadLinesBucket-100-1000 OBJECT-TYPE SYNTAX Integer32 ACCESS read-only STATUS mandatory ::= {loadPayloadLinesBuckets 1}
loadPayloadLinesBucket-1000-10000 OBJECT-TYPE SYNTAX Integer32 ACCESS read-only STATUS mandatory ::= {loadPayloadLinesBuckets 2}
loadPayloadLinesBucket-10000-100000 OBJECT-TYPE SYNTAX Integer32 ACCESS read-only STATUS mandatory ::= {loadPayloadLinesBuckets 3}
loadPayloadLinesBucket-100000-Inf OBJECT-TYPE SYNTAX Integer32 ACCESS read-only STATUS mandatory ::= {loadPayloadLinesBuckets 4}

storeTimeCount OBJECT-TYPE SYNTAX INTEGER ACCESS read-only STATUS mandatory ::= {storeTimeStats 0}
storeTimeMinUnitMS OBJECT-TYPE SYNTAX INTEGER ACCESS read-only STATUS mandatory ::= {storeTimeStats 1}
storeTimeMaxUintMS OBJECT-TYPE SYNTAX INTEGER ACCESS read-only STATUS mandatory ::= {storeTimeStats 2}
storeTimeSumUintMS OBJECT-TYPE SYNTAX INTEGER ACCESS read-only STATUS mandatory ::= {storeTimeStats 3}
storeTimeAvgUintMS OBJECT-TYPE SYNTAX INTEGER ACCESS read-only STATUS mandatory ::= {storeTimeStats 4}

storeTimeSuccessCount OBJECT-TYPE SYNTAX INTEGER ACCESS read-only STATUS mandatory ::= {storeTimeSuccessStats 0}
storeTimeSuccessMinUnitMS OBJECT-TYPE SYNTAX INTEGER ACCESS read-only STATUS mandatory ::= {storeTimeSuccessStats 1}
storeTimeSuccessMaxUintMS OBJECT-TYPE SYNTAX INTEGER ACCESS read-only STATUS mandatory ::= {storeTimeSuccessStats 2}
storeTimeSuccessSumUintMS OBJECT-TYPE SYNTAX INTEGER ACCESS read-only STATUS mandatory ::= {storeTimeSuccessStats 3}
storeTimeSuccessAvgUintMS OBJECT-TYPE SYNTAX INTEGER ACCESS read-only STATUS mandatory ::= {storeTimeSuccessStats 4}

storeTimeFailedCount OBJECT-TYPE SYNTAX INTEGER ACCESS read-only STATUS mandatory ::= {storeTimeFailedStats 0}
storeTimeFailedMinUnitMS OBJECT-TYPE SYNTAX INTEGER ACCESS read-only STATUS mandatory ::= {storeTimeFailedStats 1}
storeTimeFailedMaxUintMS OBJECT-TYPE SYNTAX INTEGER ACCESS read-only STATUS mandatory ::= {storeTimeFailedStats 2}
storeTimeFailedSumUintMS OBJECT-TYPE SYNTAX INTEGER ACCESS read-only STATUS mandatory ::= {storeTimeFailedStats 3}
storeTimeFailedAvgUintMS OBJECT-TYPE SYNTAX INTEGER ACCESS read-only STATUS mandatory ::= {storeTimeFailedStats 4}

storePayloadBytesCount OBJECT-TYPE SYNTAX INTEGER ACCESS read-only STATUS mandatory ::= {storePayloadBytesStats 0}
storePayloadBytesMin OBJECT-TYPE SYNTAX INTEGER ACCESS read-only STATUS mandatory ::= {storePayloadBytesStats 1}
storePayloadBytesMax OBJECT-TYPE SYNTAX INTEGER ACCESS read-only STATUS mandatory ::= {storePayloadBytesStats 2}
storePayloadBytesSum OBJECT-TYPE SYNTAX INTEGER ACCESS read-only STATUS mandatory ::= {storePayloadBytesStats 3}
storePayloadBytesAvg OBJECT-TYPE SYNTAX INTEGER ACCESS read-only STATUS mandatory ::= {storePayloadBytesStats 4}

storePayloadBytesBucket-NegInf-100 OBJECT-TYPE SYNTAX Integer32 ACCESS read-only STATUS mandatory ::= {storePayloadBytesBuckets 0}
storePayloadBytesBucket-100-1000 OBJECT-TYPE SYNTAX Integer32 ACCESS read-only STATUS mandatory ::= {storePayloadBytesBuckets 1}
storePayloadBytesBucket-1000-10000 OBJECT-TYPE SYNTAX Integer32 ACCESS read-only STATUS mandatory ::= {storePayloadBytesBuckets 2}
storePayloadBytesBucket-10000-100000 OBJECT-TYPE SYNTAX Integer32 ACCESS read-only STATUS mandatory ::= {storePayloadBytesBuckets 3}
storePayloadBytesBucket-100000-Inf OBJECT-TYPE SYNTAX Integer32 ACCESS read-only STATUS mandatory ::= {storePayloadBytesBuckets 4}

storePayloadLinesCount OBJECT-TYPE SYNTAX INTEGER ACCESS read-only STATUS mandatory ::= {storePayloadLinesStats 0}
storePayloadLinesMin OBJECT-TYPE SYNTAX INTEGER ACCESS read-only STATUS mandatory ::= {storePayloadLinesStats 1}
storePayloadLinesMax OBJECT-TYPE SYNTAX INTEGER ACCESS read-only STATUS mandatory ::= {storePayloadLinesStats 2}
storePayloadLinesSum OBJECT-TYPE SYNTAX INTEGER ACCESS read-only STATUS mandatory ::= {storePayloadLinesStats 3}
storePayloadLinesAvg OBJECT-TYPE SYNTAX INTEGER ACCESS read-only STATUS mandatory ::= {storePayloadLinesStats 4}

storePayloadLinesBucket-NegInf-100 OBJECT-TYPE SYNTAX Integer32 ACCESS read-only STATUS mandatory ::= {storePayloadLinesBuckets 0}
storePayloadLinesBucket-100-1000 OBJECT-TYPE SYNTAX Integer32 ACCESS read-only STATUS mandatory ::= {storePayloadLinesBuckets 1}
storePayloadLinesBucket-1000-10000 OBJECT-TYPE SYNTAX Integer32 ACCESS read-only STATUS mandatory ::= {storePayloadLinesBuckets 2}
storePayloadLinesBucket-10000-100000 OBJECT-TYPE SYNTAX Integer32 ACCESS read-only STATUS mandatory ::= {storePayloadLinesBuckets 3}
storePayloadLinesBucket-100000-Inf OBJECT-TYPE SYNTAX Integer32 ACCESS read-only STATUS mandatory ::= {storePayloadLinesBuckets 4}

deleteCount OBJECT-TYPE SYNTAX INTEGER ACCESS read-only STATUS mandatory ::= {deleteTimeStats 0}
deleteTimeMinUnitMS OBJECT-TYPE SYNTAX INTEGER ACCESS read-only STATUS mandatory ::= {deleteTimeStats 1}
deleteTimeMaxUintMS OBJECT-TYPE SYNTAX INTEGER ACCESS read-only STATUS mandatory ::= {deleteTimeStats 2}
deleteTimeSumUintMS OBJECT-TYPE SYNTAX INTEGER ACCESS read-only STATUS mandatory ::= {deleteTimeStats 3}
deleteTimeAvgUintMS OBJECT-TYPE SYNTAX INTEGER ACCESS read-only STATUS mandatory ::= {deleteTimeStats 4}

deleteSuccessCount OBJECT-TYPE SYNTAX INTEGER ACCESS read-only STATUS mandatory ::= {deleteTimeSuccessStats 0}
deleteTimeSuccessMinUnitMS OBJECT-TYPE SYNTAX INTEGER ACCESS read-only STATUS mandatory ::= {deleteTimeSuccessStats 1}
deleteTimeSuccessMaxUintMS OBJECT-TYPE SYNTAX INTEGER ACCESS read-only STATUS mandatory ::= {deleteTimeSuccessStats 2}
deleteTimeSuccessSumUintMS OBJECT-TYPE SYNTAX INTEGER ACCESS read-only STATUS mandatory ::= {deleteTimeSuccessStats 3}
deleteTimeSuccessAvgUintMS OBJECT-TYPE SYNTAX INTEGER ACCESS read-only STATUS mandatory ::= {deleteTimeSuccessStats 4}

deleteFailedCount OBJECT-TYPE SYNTAX INTEGER ACCESS read-only STATUS mandatory ::= {deleteTimeFailedStats 0}
deleteTimeFailedMinUnitMS OBJECT-TYPE SYNTAX INTEGER ACCESS read-only STATUS mandatory ::= {deleteTimeFailedStats 1}
deleteTimeFailedMaxUintMS OBJECT-TYPE SYNTAX INTEGER ACCESS read-only STATUS mandatory ::= {deleteTimeFailedStats 2}
deleteTimeFailedSumUintMS OBJECT-TYPE SYNTAX INTEGER ACCESS read-only STATUS mandatory ::= {deleteTimeFailedStats 3}
deleteTimeFailedAvgUintMS OBJECT-TYPE SYNTAX INTEGER ACCESS read-only STATUS mandatory ::= {deleteTimeFailedStats 4}

END
